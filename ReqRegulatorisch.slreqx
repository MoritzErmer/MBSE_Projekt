# ReqRegulatorisch

## ReqRegulatorisch: References to ReqRegulatorisch.docx (Container)
Read-only references to Microsoft Word document.

### 1. Fahrzeugtechnische Anforderungen (§ 1 - § 3) (Functional)

#### EKF-01: Bauartbedingte Höchstgeschwindigkeit (Functional)
EKF-01: Bauartbedingte Höchstgeschwindigkeit
Zusammenfassung: Geschwindigkeit zwischen 6 km/h und 20 km/h.
Beschreibung: Das Fahrzeug muss eine bauartbedingte Höchstgeschwindigkeit von nicht weniger als 6 km/h und nicht mehr als 20 km/h aufweisen.
- Rationale: § 1 Abs. 1 eKFV

#### EKF-02: Nenndauerleistung (Functional)
EKF-02: Nenndauerleistung
Zusammenfassung: Leistungsbegrenzung 500W / 1400W.
Beschreibung: Die Nenndauerleistung darf 500 Watt nicht überschreiten (1400 Watt bei selbstbalancierenden Fahrzeugen mit mindestens 60 % Stabilisierungsanteil).
Norm: DIN EN 15194 / UNECE R85.

#### EKF-03: Abmessungen und Masse (Functional)
EKF-03: Abmessungen und Masse
Zusammenfassung: Max. 55kg Masse und definierte Maße.
Beschreibung: Gesamtbreite max. 700 mm, Gesamthöhe max. 1400 mm, Gesamtlänge max. 2000 mm. Fahrzeugmasse ohne Fahrer maximal 55 kg.

### 2. Sicherheitstechnische Systeme (§ 4 - § 7) (Functional)

#### EKF-04: Verzögerungseinrichtung (Bremsen) (Functional)
EKF-04: Verzögerungseinrichtung (Bremsen)
Zusammenfassung: Zwei unabhängige Bremsen mit 3,5 m/s².
Beschreibung: Das Fahrzeug muss mit zwei voneinander unabhängigen Bremsen ausgerüstet sein, die bis zur Maximalgeschwindigkeit wirken und eine Verzögerung von mindestens 3,5 m/s² erreichen.

#### EKF-05: Lichttechnische Einrichtungen (Functional)
EKF-05: Lichttechnische Einrichtungen
Zusammenfassung: Beleuchtung nach StVZO.
Beschreibung: Ausrüstung mit Scheinwerfer (weiß), Schlussleuchte (rot) und seitlichen gelben Rückstrahlern (oder weißen Reflexstreifen an Reifen/Felgen).
Norm: UNECE R50.

#### EKF-06: Totmann-Schalter (Antriebsdeaktivierung) (Functional)
EKF-06: Totmann-Schalter (Antriebsdeaktivierung)
Zusammenfassung: Motor-Nullstellung innerhalb von 1 Sekunde.
Beschreibung: Das Bedienelement zur Steuerung der Motorleistung muss sich innerhalb einer Sekunde selbstständig in Nullstellung zurückstellen, wenn der Fahrer es loslässt.

### 3. Prüfbedingungen und Fahrdynamik (Anlage) (Functional)

#### ANL-01: Umgebungsbedingungen für Tests (Functional)
ANL-01: Umgebungsbedingungen für Tests
Zusammenfassung: Temperatur und Untergrund.
Beschreibung: Prüfungen auf ebener, trockener Beton-/Asphaltoberfläche. Steigung <= 1%. Temperatur zwischen 0 °C und 45 °C. Akkuladestand >= 75 %.

#### ANL-02: Dynamische Stabilität (Hindernisse) (Functional)
ANL-02: Dynamische Stabilität (Hindernisse)
Zusammenfassung: Überfahren von Kanten und Vertiefungen.
Beschreibung: Stabiles Überfahren einer 3 cm Bordsteinkante (Winkel 90° und 45°) sowie Durchfahren einer 5 cm tiefen Vertiefung bei Höchstgeschwindigkeit.

### 4. Technische Referenznormen (Functional)

#### NORM-01: Elektromagnetische Verträglichkeit (EMV) (Functional)
NORM-01: Elektromagnetische Verträglichkeit (EMV)
Beschreibung: Nachweis der Störfestigkeit und Emissionsgrenzwerte gemäß UNECE Regelung Nr. 10.

#### NORM-02: Funktionale Sicherheit (ISO 13849) (Functional)
NORM-02: Funktionale Sicherheit (ISO 13849)
Beschreibung: Auslegung sicherheitskritischer Funktionen (Bremse/Gas) nach dem Stand der Technik (Performance Level r).
